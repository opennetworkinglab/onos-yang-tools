module Test {
    yang-version 1;
    namespace http://huawei.com;
    prefix Ant;
    typedef invalid-interval {
        type string {
            length "1..100" {
                description "length-description typedef";
                reference "reference typedef";
            }
         }
    }
    leaf xyz {
       type invalid-interval {
           length "2..100"{
                description "length-description type";
                reference "reference type";
            }
       }
    }
}
