module Test {
    yang-version 1;
    namespace urn:ietf:params:xml:ns:yang:ietf-ospf;
    prefix On;
    deviation /base:system/base:daytime {
        description "desc";
        reference "ref";
        deviate not-supported;
    }
}
