module TestUnique {
    yang-version 1;
    namespace http://huawei.com;
    prefix Anim;
    list resources {
        key "count";
        leaf count {
            type int;
        }
        unique "animal/mammal/abc";
        container animal {
            list mammal {
                key "abc";
                leaf abc {
                    type "String";
                }
            }
        }
    }
}
