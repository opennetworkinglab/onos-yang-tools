module Test {
    yang-version 1;
    namespace "http://huawei.com";
    prefix Ant;
    list interface-switching-capability {
         when "../switching-capability = TDM" {
                 description "Valid only for TDM";
         }
         key "switching-capability";
         description
           "List of Interface Switching Capabilities Descriptors (ISCD)
            for this link.";
         reference
           "RFC3471: Generalized Multi-Protocol Label Switching (GMPLS)
            Signaling Functional Description.
            RFC4203: OSPF Extensions in Support of Generalized
            Multi-Protocol Label Switching (GMPLS).";
         leaf switching-capability {
           type string;
           description
             "Switching Capability for this interface.";
         }
     }
     container time-division-multiplex-capable {
         when "../switching-capability = TDM" {
             description "Valid only for TDM";
         }
         description
             "Interface has time-division multiplex capabilities.";

         leaf minimum-lsp-bandwidth {
             type decimal64 {
                fraction-digits 4;
             } 
         }
     }
}
