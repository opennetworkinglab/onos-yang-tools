module Test {
    yang-version 1;
    namespace http://huawei.com;
    prefix Ant;
    leaf message {
        type binary {
            length "4" {
                description "binary description";
                reference "binary reference";
            }
        }
    }
}
