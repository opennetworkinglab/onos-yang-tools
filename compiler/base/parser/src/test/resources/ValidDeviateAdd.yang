module Test {
    yang-version 1;
    namespace urn:ietf:params:xml:ns:yang:ietf-ospf;
    prefix On;
    deviation /base:system/base:user/base:type {
        deviate add {
            units "units";
            must "/base:system";
            unique "id";
            default "admin";
            config "true";
            mandatory "true";
            min-elements "0";
            max-elements "12343";
        }
    }
}
