module Test {
    yang-version 1;
    namespace urn:ietf:params:xml:ns:yang:ietf-ospf;
    prefix On;
    deviation "/base:system" {
        deviate delete {
           units "units";
           must "daytime or time";
           unique "id";
           default "defaultValue";
        }
    }
}
