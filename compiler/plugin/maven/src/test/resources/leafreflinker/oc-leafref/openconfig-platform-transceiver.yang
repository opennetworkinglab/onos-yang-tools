module openconfig-platform-transceiver {

  yang-version "1";

  namespace "http://openconfig.net/yang/platform/transceiver";

  prefix "oc-transceiver";

  import openconfig-platform { prefix oc-platform; }
  import openconfig-interfaces { prefix oc-if; }

  revision 2016-12-22;


  grouping physical-channel-top {
    container physical-channels {
      list channel {
        key "index";

        leaf index {
          type string;
        }
    }
  }
  }

  grouping port-transceiver-top {
    container transceiver {
      uses physical-channel-top;
    }
  }

  augment "/oc-platform:components/oc-platform:component" {
    uses port-transceiver-top;
  }

  augment "/oc-if:interfaces/oc-if:interface/oc-if:state" {
    leaf-list physical-channel {
      type leafref {
        path "/oc-platform:components/" +
          "oc-platform:component[oc-platform:name=current()/../oc-platform:hardware-port]/" +
          "oc-transceiver:transceiver/" +
          "oc-transceiver:physical-channels/oc-transceiver:channel/" +
          "oc-transceiver:index";
      }
    }
  }
}
