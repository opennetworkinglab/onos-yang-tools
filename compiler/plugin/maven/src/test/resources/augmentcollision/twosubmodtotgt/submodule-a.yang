submodule sub-module-a {

    belongs-to "module-a" {
        prefix "mod-a";
    }

    import module-b {
        prefix mod-b;
    }

    augment "/mod-b:cont" {
        container val {
            leaf arg {
                type string;
            }
        }
    }
}
