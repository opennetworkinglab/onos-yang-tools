module module-a {

    namespace "urn:ietf:params:xml:ns:yang:module:a";

    prefix mod-a;

    import module-b {
        prefix mod-b;
    }

    augment "/mod-b:cont" {
        container val {
            leaf arg {
                type string;
            }
        }
    }
}
