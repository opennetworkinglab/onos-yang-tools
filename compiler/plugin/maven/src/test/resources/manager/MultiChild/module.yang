module test5 {
    namespace "multi:test5:test";
    prefix test ;

    revision "2016-07-04" {
             description "Initial revision.";
    }
    typedef typedef1 {
       type int32;
    }
    typedef typedef2 {
       type int32;
    }
    typedef typedef3 {
       type int32;
    }

}
