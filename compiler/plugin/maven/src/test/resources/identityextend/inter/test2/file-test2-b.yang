module file-test2-b {
    yang-version 1;
    namespace
      "http://test2.org/ns/file/b";
    prefix t2fb;

    revision "2009-11-21" {
      description
        "sample module in progress.";
    }

    identity id1;

    identity id5 {
       base id1;
    }

    identity id6 {
       base id1;
    }
}
