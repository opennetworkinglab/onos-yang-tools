module file-test2-a {
    yang-version 1;
    namespace
      "http://test2.org/ns/file/a";
    prefix t2fa;

    import file-test2-b {
        prefix t2fb;
    }

    revision "2009-11-21" {
      description
        "sample module in progress.";
    }

    identity id2 {
       base "t2fb:id1";
    }

    identity id3 {
       base "id2";
    }

    identity id4 {
       base "id2";
    }
}
