module IdentityTypedef {
    yang-version 1;
    namespace http://huawei.com;
    prefix IdentityTypedef;

    identity ref-address-family {

    }

    identity ipv4-address-family {
        base ref-address-family;
    }

    identity ipv6-address-family {
        base ref-address-family;
    }

    typedef type2 {
        type identityref {
             base ipv4-address-family;
        }
    }

    typedef type3 {
        type union {
            type type2;
            type identityref {
                 base ipv4-address-family;
            }
        }
    }

    typedef type4 {
        type union {
            type identityref {
                base ipv4-address-family;
            }
            type identityref {
                base ipv6-address-family;
            }
        }
    }

    leaf tunnel {
        type type15;
    }

    leaf-list network-ref {
        type type15;
    }

    typedef type15 {
        type identityref {
            base ref-address-family;
        }
    }
}
