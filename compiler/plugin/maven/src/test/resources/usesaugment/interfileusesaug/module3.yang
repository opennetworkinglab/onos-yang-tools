module module3 {
    yang-version 1;

    namespace
        "http://org/ns/module3";

    prefix m3;

    import module2 {
        prefix m2;
    }

    grouping group {
        leaf l1 {
            type int8;
        }

        container cont2 {
            leaf-list ll1 {
                type decimal64 {
                    fraction-digits 1;
                }
            }
            uses m2:group2 {
                augment "cont3" {
                    container cont4 {
                        container cont5 {
                            uses m2:group3 {
                                augment "cont6" {
                                    leaf ll5 {
                                        type uint64;
                                    }
                                }
                            }
                        }
                    }
                }

                augment "interface" {
                    case vlan {
                        container vl {
                        }
                    }
                }

                augment "interface/physical" {
                    list interfaces {
                        key "int-name";
                        leaf int-name {
                            type string;
                        }
                    }
                }
            }
        }
    }
}
