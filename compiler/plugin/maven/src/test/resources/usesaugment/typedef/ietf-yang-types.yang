module ietf-yang-types {
    yang-version 1;

    namespace
        "http://org/ns/yang-types";

    prefix type;

    typedef date-and-time {
        type string {
            pattern '\d{4}-\d{2}-\d{2}T\d{2}:\d{2}:\d{2}(\.\d+)?'
            + '(Z|[\+\-]\d{2}:\d{2})';
        }
    }

    typedef counter64 {
        type uint64;
    }

    typedef timeticks {
        type uint32;
    }
}
