module Sfc {
    yang-version 1;
    namespace http://huawei.com;
    prefix Ant;
    leaf test{
        type string;
    }
    leaf myenum {
      type enumeration {
         enum zero;
         enum one;
         enum "twenty three";
         enum seven {
              value 7;
             }
         }
     }
}
