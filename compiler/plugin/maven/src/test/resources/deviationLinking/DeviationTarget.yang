module Test2 {
    yang-version 1;
    namespace "test2:deviation";
    prefix test;
    container ospf {
        leaf process-id {
            type "uint16";
            units "seconds";
            status current;
            reference "RFC 6020";
            default "1";
         }
    }

    container valid {
        leaf invalid-interval {
            type "uint16";
            units "seconds";
            status current;
            reference "RFC 6020";
         }
    }
}
