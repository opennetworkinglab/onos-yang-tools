module ietf-network-topology {
   yang-version 1;
   namespace "urn:ietf:params:xml:ns:yang:ietf-network-topology";
   prefix lnk;

   import ietf-network {
     prefix nd;
   }

   revision 2017-03-01 {
     reference
       "draft-ietf-i2rs-yang-network-topo-12";
   }

   augment "/nd:networks/nd:network" {
     list link {
       key "link-id";
       leaf link-id {
         type string;
       }
     }
   }
 }
