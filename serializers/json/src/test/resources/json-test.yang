module jsonlist {

    yang-version 1;

    namespace "jsonlist";

    prefix "l";

    organization "ON-LAB";

    description "This module defines for list.";

    revision "2016-06-24" {
        description "Initial revision.";
    }

  container top1 {
    list l1 {
        key "k1 k2 k3";
            leaf k1 {
               type string;
            }

            leaf k2 {
              type string;
            }

            leaf k3 {
              type string;
            }

            container c1 {
                leaf leaf_c1 {
                  type string;
                }
            }
    }

    container c2 {
      leaf-list leaflist1 {
          type string;
      }
      leaf leaf1 {
         type int8;
      }

      leaf leaf2 {
        type int16;
      }

      leaf leaf3 {
        type int32;
      }

      leaf leaf4 {
         type uint8;
      }

      leaf leaf5 {
        type uint16;
      }

      leaf leaf6 {
        type uint32;
      }

      leaf leaf7 {
        type int64;
      }

      leaf leaf8 {
        type uint64;
      }

      leaf leaf9 {
        type boolean;
      }

      leaf leaf10 {
       type decimal64 {
           fraction-digits 1;
       }
      }

      leaf-list ll1 {
          type int8;
      }

      leaf-list ll2 {
          type int16;
      }

      leaf-list ll3 {
          type int32;
      }

      leaf-list ll4 {
          type uint8;
      }

      leaf-list ll5 {
          type uint16;
      }

      leaf-list ll6 {
          type uint32;
      }

      leaf-list ll7 {
          type int64;
      }

      leaf-list ll8 {
          type uint64;
      }

      leaf-list ll9 {
          type boolean;
      }

      leaf-list ll10 {
        type decimal64 {
            fraction-digits 1;
        }
      }
    }
  }
}
