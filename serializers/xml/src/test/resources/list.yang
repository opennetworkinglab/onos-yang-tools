module list {

    yang-version 1;

    namespace "yrt:list";

    prefix "l";

    organization "ON-LAB";

    description "This module defines for list.";

    revision "2016-06-24" {
        description "Initial revision.";
    }

    list l1 {
        key "k1 k2 k3";
            leaf k1 {
               type string;
            }

            leaf k2 {
              type string;
            }

            leaf k3 {
              type string;
            }

            container c1 {
                leaf leaf_c1 {
                  type string;
                }
            }
    }

    leaf-list leaf1 {
        type string;
    }

    container c2 {
       config false;
       list l2 {
          key "m1 m2";
          leaf m1 {
              type string;
          }

          leaf m2 {
              type string;
          }
       }
    }
}
