module ModuleListAndKey {
    yang-version 1;
    namespace "yms:test:ytb:tree:builder:for:list:having:list";
    prefix "sch";
    revision "2016-08-26";

    list modKey {
        key "types";
        leaf types {
            type int32;
        }
    }

    typedef tdef1 {
        type union {
            type uint64;
            type enumeration {
                enum ten {
                    value "10";
                }
                enum hundred {
                    value "100";
                }
                enum thousand {
                    value "1000";
                }
            }
        }
    }

    typedef bitdef {
        type bits {
            bit str;
            bit num;
        }
    }

    typedef id {
        type union {
            type identityref {
                base int;
            }
            type boolean;
        }
    }

    identity int {
        description "type value";
    }

    identity phy {
        base int;
    }

    identity vir {
        base int;
    }

    list type {
        key "leaf1 leaf2 leaf3 leaf4 leaf5 leaf6 leaf7 leaf8 leaf9";

        leaf leaf1 {
            type union {
                type int8;
                type uint8;
            }
        }

        leaf leaf2 {
            type identityref {
                base int;
            }
        }

        leaf leaf3 {
            type tdef1;
        }

        leaf leaf4 {
            type leafref {
                path "../leaf2";
            }
        }

        leaf leaf5 {
            type instance-identifier;
        }

        leaf leaf6 {
            type enumeration {
                enum enum1;
                enum enum2;
            }
        }

        leaf leaf7 {
            type bitdef;
        }

        leaf leaf8 {
            type binary;
        }

        leaf leaf9 {
            type id;
        }

        container con1 {
            leaf-list ll {
                type tdef1;
            }
        }
    }

    leaf-list tri {
        type identityref {
            base int;
        }
    }

    leaf-list ll1 {
        type union {
            type int8;
            type uint8;
        }
    }

    leaf-list ll2 {
        type identityref {
            base int;
        }
    }

    leaf-list ll3 {
        type tdef1;
    }

    leaf-list ll4 {
        type leafref {
            path "../ll2";
        }
    }

    leaf-list ll5 {
        type instance-identifier;
    }

    leaf-list ll6 {
        type enumeration {
            enum enum1;
            enum enum2;
        }
    }

    leaf-list ll7 {
        type bitdef;
    }

    leaf-list ll8 {
        type binary;
    }

    leaf-list ll9 {
        type id;
    }

    container val {
    }
}
