module actn-ietf-te-types {
   namespace "urn:ietf:params:xml:ns:yang:actn-ietf-te-types";

   /* Replace with IANA when assigned */
   prefix "te-types";

   import yrt-ietf-inet-types {
     prefix inet;
   }

   import yrt-ietf-yang-types {
     prefix "yang";
   }

   import actn-ietf-routing-types {
     prefix "rt-types";
   }

   organization
     "IETF Traffic Engineering Architecture and Signaling (TEAS)
      Working Group";

   contact
     "WG Web:   <http://tools.ietf.org/wg/teas/>
      WG List:  <mailto:teas@ietf.org>

      WG Chair: Lou Berger
                <mailto:lberger@labn.net>

      WG Chair: Vishnu Pavan Beeram
                <mailto:vbeeram@juniper.net>

      Editor:   Tarek Saad
                <mailto:tsaad@cisco.com>

      Editor:   Rakesh Gandhi
                <mailto:rgandhi@cisco.com>

      Editor:   Vishnu Pavan Beeram
                <mailto:vbeeram@juniper.net>

      Editor:   Himanshu Shah
                <mailto:hshah@ciena.com>

      Editor:   Xufeng Liu
                <mailto:xufeng.liu@ericsson.com>

      Editor:   Xia Chen
                <mailto:jescia.chenxia@huawei.com>

      Editor:   Raqib Jones
                <mailto:raqib@Brocade.com>

      Editor:   Bin Wen
                <mailto:Bin_Wen@cable.comcast.com>";

   description
     "This module contains a collection of generally
     useful TE specific YANG data type defintions.";

   revision "2017-03-10" {
     description "Latest revision of TE types";
     reference "RFC3209";
   }

   /*
    * Identities
    */

   identity path-computation-method {
     description
      "base identity for supported path computation
       mechanisms";
   }

   identity path-locally-computed {
     base path-computation-method;
     description
       "indicates a constrained-path LSP in which the
       path is computed by the local LER";
   }

   identity path-externally-queried {
     base path-computation-method;
     description
      "Constrained-path LSP in which the path is
       obtained by querying an external source, such as a PCE server.
       In the case that an LSP is defined to be externally queried, it
       may also have associated explicit definitions (which are provided
       to the external source to aid computation); and the path that is
       returned by the external source is not required to provide a
       wholly resolved path back to the originating system - that is to
       say, some local computation may also be required";
   }

   identity path-explicitly-defined {
     base path-computation-method;
     description
      "constrained-path LSP in which the path is
       explicitly specified as a collection of strict or/and loose
       hops";
   }

   typedef te-ds-class {
     type uint8 {
       range "0..7";
     }
     description
       "The Differentiatied Class-Type of traffic.";
     reference "RFC4124: section-4.3.1";
   }

   typedef te-hop-type {
     type enumeration {
       enum LOOSE {
         description
           "loose hop in an explicit path";
       }
       enum STRICT {
         description
           "strict hop in an explicit path";
       }
     }
     description
      "enumerated type for specifying loose or strict
       paths";
   }

   identity LSP_METRIC_TYPE {
     description
       "Base identity for types of LSP metric specification";
   }

   identity LSP_METRIC_RELATIVE {
     base LSP_METRIC_TYPE;
     description
       "The metric specified for the LSPs to which this identity refers
       is specified as a relative value to the IGP metric cost to the
       LSP's tail-end.";
   }

   identity LSP_METRIC_ABSOLUTE {
     base LSP_METRIC_TYPE;
     description
       "The metric specified for the LSPs to which this identity refers
       is specified as an absolute value";
   }

   identity LSP_METRIC_INHERITED {
     base LSP_METRIC_TYPE;
     description
       "The metric for for the LSPs to which this identity refers is
       not specified explicitly - but rather inherited from the IGP
       cost directly";
   }

   identity tunnel-type {
     description
       "Base identity from which specific tunnel types are
       derived.";
   }

   identity tunnel-p2p {
     base tunnel-type;
     description
       "TE point-to-point tunnel type.";
   }

   identity tunnel-p2mp {
     base tunnel-type;
     description
       "TE point-to-multipoint tunnel type.";
   }

   identity tunnel-action-type {
     description
       "Base identity from which specific tunnel action types
        are derived.";
   }

   identity tunnel-action-resetup {
     base tunnel-action-type;
     description
       "TE tunnel action resetup. Tears the
       tunnel's current LSP (if any) and
       attempts to re-establish a new LSP";
   }

   identity tunnel-action-reoptimize {
     base tunnel-action-type;
     description
       "TE tunnel action reoptimize.
        Reoptimizes placement of the tunnel LSP(s)";
   }

   identity tunnel-action-switchpath {
     base tunnel-action-type;
     description
       "TE tunnel action reoptimize
        Switches the tunnel's LSP to use the specified path";
   }

   identity te-action-result {
     description
       "Base identity from which specific TE action results
        are derived.";
   }

   identity te-action-success {
     base te-action-result;
     description "TE action successul.";
   }

   identity te-action-fail {
     base te-action-result;
     description "TE action failed.";
   }

   identity tunnel-action-inprogress {
     base te-action-result;
     description "TE action inprogress.";
   }

   identity state-type {
     description
       "Base identity for TE states";
   }

   identity state-up {
     base state-type;
     description
       "State up";
   }

   identity state-down {
     base state-type;
     description
       "State down";
   }

   identity prov-state-type {
     description
       "Base identity for TE tunnel provisioning states";
   }

   identity prov-state-down {
     base prov-state-type;
     description
       "Provisioning state down";
   }

   identity prov-state-computing {
     base prov-state-type;
     description
       "Provisioning state computing";
   }

   identity prov-state-computed-ok {
     base prov-state-type;
     description
       "Provisioning state computation success";
   }

   identity prov-state-computed-fail {
     base prov-state-type;
     description
       "Provisioning state computation failure";
   }

   identity prov-state-setting-up {
     base prov-state-type;
     description
       "Provisioning state setting-up";
   }

   identity prov-state-setup-fail {
     base prov-state-type;
     description
       "Provisioning state setup failure";
   }

   identity prov-state-active {
     base prov-state-type;
     description
       "Provisioning state active (setup ok)";
   }

   identity prov-state-tearing-down {
     base prov-state-type;
     description
       "Provisioning state tearing down";
   }

   identity path-invalidation-action-type {
     description
       "Base identity for TE path invalidation action types";
   }

   identity path-invalidation-action-drop-type {
     base path-invalidation-action-type;
     description
       "TE path invalidation action drop";
   }

   identity path-invalidation-action-drop-tear {
     base path-invalidation-action-type;
     description
       "TE path invalidation action tear";
   }

   identity lsp-prot-type {
     description
       "Base identity from which LSP protection types are
       derived.";
   }

   identity lsp-prot-unprotected {
     base lsp-prot-type;
     description
       "LSP protection 'Unprotected'";
     reference "RFC4872";
   }

   identity lsp-prot-reroute-extra {
     base lsp-prot-type;
     description
       "LSP protection '(Full) Rerouting'";
     reference "RFC4872";
   }

   identity lsp-prot-reroute {
     base lsp-prot-type;
     description
       "LSP protection 'Rerouting without Extra-Traffic'";
     reference "RFC4872";
   }

   identity lsp-prot-1-for-n {
     base lsp-prot-type;
     description
       "LSP protection '1:N Protection with Extra-Traffic'";
     reference "RFC4872";
   }

   identity lsp-prot-unidir-1-to-1 {
     base lsp-prot-type;
     description
       "LSP protection '1+1 Unidirectional Protection'";
     reference "RFC4872";
   }

   identity lsp-prot-bidir-1-to-1 {
     base lsp-prot-type;
     description
       "LSP protection '1+1 Bidirectional Protection'";
     reference "RFC4872";
   }

   identity switching-capabilities {
     description
       "Base identity for interface switching capabilities";
   }

   identity switching-psc1 {
     base switching-capabilities;
     description
       "Packet-Switch Capable-1 (PSC-1)";
   }

   identity switching-evpl {
     base switching-capabilities;
     description
       "Ethernet Virtual Private Line (EVPL)";
   }

   identity switching-l2sc {
     base switching-capabilities;
     description
       "Layer-2 Switch Capable (L2SC)";
   }

   identity switching-tdm {
     base switching-capabilities;
     description
       "Time-Division-Multiplex Capable (TDM)";
   }

   identity switching-otn {
     base switching-capabilities;
     description
       "OTN-TDM capable";
   }

   identity switching-dcsc {
     base switching-capabilities;
     description
       "Data Channel Switching Capable (DCSC)";
   }

   identity switching-lsc {
     base switching-capabilities;
     description
       "Lambda-Switch Capable (LSC)";
   }

   identity switching-fsc {
     base switching-capabilities;
     description
       "Fiber-Switch Capable (FSC)";
   }

   identity lsp-encoding-types {
     description
       "Base identity for encoding types";
   }

   identity lsp-encoding-packet {
     base lsp-encoding-types;
     description
       "Packet LSP encoding";
   }

   identity lsp-encoding-ethernet {
     base lsp-encoding-types;
     description
       "Ethernet LSP encoding";
   }

   identity lsp-encoding-pdh {
     base lsp-encoding-types;
     description
       "ANSI/ETSI LSP encoding";
   }

   identity lsp-encoding-sdh {
     base lsp-encoding-types;
     description
       "SDH ITU-T G.707 / SONET ANSI T1.105 LSP encoding";
   }

   identity lsp-encoding-digital-wrapper {
     base lsp-encoding-types;
     description
       "Digital Wrapper LSP encoding";
   }

   identity lsp-encoding-lambda {
     base lsp-encoding-types;
     description
       "Lambda (photonic) LSP encoding";
   }

   identity lsp-encoding-fiber {
     base lsp-encoding-types;
     description
       "Fiber LSP encoding";
   }

   identity lsp-encoding-fiber-channel {
     base lsp-encoding-types;
     description
       "FiberChannel LSP encoding";
   }

   identity lsp-encoding-oduk {
     base lsp-encoding-types;
     description
       "G.709 ODUk (Digital Path)LSP encoding";
   }

   identity lsp-encoding-optical-channel {
     base lsp-encoding-types;
     description
       "Line (e.g., 8B/10B) LSP encoding";
   }

   identity lsp-encoding-line {
     base lsp-encoding-types;
     description
       "Line (e.g., 8B/10B) LSP encoding";
   }

   identity path-signaling-type {
     description
       "Base identity from which specific path signaling
        types are derived.";
   }

   identity path-signaling-rsvpte {
     base tunnel-type;
     description
       "RSVP-TE path signaling type";
   }

   identity path-signaling-sr {
     base tunnel-type;
     description
       "Segment-routing path signaling type";
   }

   identity te-path-setup-protocol {
     description
       "base identity for supported TE LSPs signaling
        protocols";
   }

   identity te-path-setup-static {
     base te-path-setup-protocol;
     description
       "Static LSP provisioning";
   }

   identity te-path-setup-rsvp {
     base te-path-setup-protocol;
     description
       "RSVP-TE signaling protocol";
   }

   identity te-path-setup-sr {
     base te-path-setup-protocol;
     description
       "Segment routing";
   }

   /* TE basic features */
   feature p2mp-te {
     description
       "Indicates support for P2MP-TE";
   }

   feature frr-te {
     description
       "Indicates support for TE FastReroute (FRR)";
   }

   feature extended-admin-groups {
     description
       "Indicates support for TE link extended admin
       groups.";
   }

   feature named-path-affinities {
     description
       "Indicates support for named path affinities";
   }

   feature named-extended-admin-groups {
     description
       "Indicates support for named extended admin groups";
   }

   feature named-srlg-groups {
     description
       "Indicates support for named SRLG groups";
   }

   feature named-path-constraints {
     description
       "Indicates support for named path constraints";
   }

   grouping explicit-route-hop_config {
     description
       "The explicit route subobject grouping";
     leaf index {
       type uint32;
       description "ERO subobject index";
     }
     choice type {
       description
         "The explicit route subobject type";
       case ip-address {
         description
           "IP address explicit route subobject";
         container ip-address-hop {
           description "IP address hop type";
           leaf address {
             type inet:ip-address;
             description
               "ERO IP address.";
           }
           leaf hop-type {
             type te-hop-type;
               description
                 "strict or loose hop";
           }
         }
       }
       case as-number {
         container as-number-hop {
           leaf as-number {
             type binary {
               length 16;
             }
             description "AS number";
           }
           leaf hop-type {
             type te-hop-type;
               description
                 "strict or loose hop";
           }
           description
             "Autonomous System explicit route subobject";
         }
       }
       case unnumbered-link {
         container unnumbered-hop {
           leaf router-id {
             type inet:ip-address;
             description
               "A router-id address";
           }
           leaf interface-id {
             type uint32;
             description "The interface identifier";
           }
           leaf hop-type {
             type te-hop-type;
               description
                 "strict or loose hop";
           }
           description
             "Unnumbered link explicit route subobject";
           reference
             "RFC3477: Signalling Unnumbered Links in
             RSVP-TE";
         }
       }
       case label {
         container label-hop {
           description "Label hop type";
           leaf value {
             type rt-types:generalized-label;
             description "the label value";
           }
         }
         description
           "The Label ERO subobject";
       }
       case sid {
         container sid-hop {
           description "foo";
           leaf sid {
             type rt-types:generalized-label;
             description "Segment-routing identifier";
           }
         }
         description "Segment-routing identifier";
       }
     }
   }

   grouping explicit-route-hop {
     description "Explicit route hop grouping";
     container config {
       description
         "Configuration parameters for the explicit route hop";
       uses explicit-route-hop_config;
     }
     container state {
       config false;
       description
         "State parameters for the explicit route hop";
       uses explicit-route-hop_config;
     }
   }

   grouping record-route-subobject {
     description
       "The record route subobject grouping";
     choice type {
       description
         "The record route subobject type";
       case ip-address {
         leaf ip-address {
           type inet:ip-address;
           description
             "RRO IP address subobject.";
         }
         leaf ip-flags {
           type binary {
             length 8;
           }
           description
             "RRO IP address sub-object flags";
           reference "RFC3209";
         }
       }
       case unnumbered-link {
         leaf router-id {
           type inet:ip-address;
           description
             "A router-id address";
         }
         leaf interface-id {
           type uint32;
           description "The interface identifier";
         }
         description
           "Unnumbered link record route subobject";
         reference
           "RFC3477: Signalling Unnumbered Links in
            RSVP-TE";
       }
       case label {
         leaf value {
           type rt-types:generalized-label;
           description "the label value";
         }
         leaf label-flags {
           type binary {
             length 8;
           }
           description
             "Label sub-object flags";
           reference "RFC3209";
         }
         description
           "The Label ERO subobject";
       }
     }
   }

   identity route-usage-type {
     description
       "Base identity for route usage";
   }

   identity route-include-ero {
     base route-usage-type;
     description
       "Include ERO from route";
   }

   identity route-exclude-ero {
     base route-usage-type;
     description
       "Exclude ERO from route";
   }

   identity route-exclude-srlg {
     base route-usage-type;
     description
       "Exclude SRLG from route";
   }

   identity path-metric-type {
     description
       "Base identity for path metric type";
   }

   identity path-metric-te {
     base path-metric-type;
     description
       "TE path metric";
   }

   identity path-metric-igp {
     base path-metric-type;
     description
       "IGP path metric";
   }

   identity path-metric-hop {
     base path-metric-type;
     description
       "Hop path metric";
   }

   identity path-metric-delay {
     base path-metric-type;
     description
       "Delay path metric";
   }

   identity path-tiebreaker-type {
     description
       "Base identity for path tie-breaker type";
   }

   identity path-tiebreaker-minfill {
     base path-tiebreaker-type;
     description
       "Min-Fill LSP path placement";
   }

   identity path-tiebreaker-maxfill {
     base path-tiebreaker-type;
     description
       "Max-Fill LSP path placement";
   }

   identity path-tiebreaker-randoom {
     base path-tiebreaker-type;
     description
       "Random LSP path placement";
   }

   identity bidir-provisioning-mode {
     description
       "Base identity for bidirectional provisioning
       mode.";
   }

   identity bidir-provisioning-single-sided {
     base bidir-provisioning-mode;
     description
       "Single-sided bidirectional provioning mode";
   }

   identity bidir-provisioning-double-sided {
     base bidir-provisioning-mode;
     description
       "Double-sided bidirectional provioning mode";
   }

   identity bidir-association-type {
     description
       "Base identity for bidirectional association type";
   }

   identity bidir-assoc-corouted {
     base bidir-association-type;
     description
       "Co-routed bidirectional association type";
   }

   identity bidir-assoc-non-corouted {
     base bidir-association-type;
     description
       "Non co-routed bidirectional association type";
   }

   identity resource-affinities-type {
     description
       "Base identity for resource affinities";
   }

   identity resource-aff-include-all {
     base resource-affinities-type;
     description
       "The set of attribute filters associated with a
       tunnel all of which must be present for a link
       to be acceptable";
   }

   identity resource-aff-include-any {
     base resource-affinities-type;
     description
       "The set of attribute filters associated with a
       tunnel any of which must be present for a link
       to be acceptable";
   }

   identity resource-aff-exclude-any {
     base resource-affinities-type;
     description
       "The set of attribute filters associated with a
       tunnel any of which renders a link unacceptable";
   }

   identity te-optimization-criterion {
     description
       "Base identity for TE optimization criterion.";
     reference
       "RFC3272: Overview and Principles of Internet Traffic
        Engineering.";
   }

   identity not-optimized {
     base te-optimization-criterion;
     description "Optimization is not applied.";
   }

   identity cost {
     base te-optimization-criterion;
     description "Optimized on cost.";
   }

   identity delay {
     base te-optimization-criterion;
     description "Optimized on delay.";
   }

   /*
    * Typedefs
    */

   typedef percentage {
     type uint8 {
       range "0..100";
     }
     description
       "Integer indicating a percentage value";
   }

   typedef performance-metric-normality {
     type enumeration {
       enum "unknown" {
         value 0;
         description
           "Unknown.";
       }
       enum "normal" {
         value 1;
         description
           "Normal.";
       }
       enum "abnormal" {
         value 2;
         description
           "Abnormal. The anomalous bit is set.";
       }
     }
     description
       "Indicates whether a performance metric is normal, abnormal, or
        unknown.";
     reference
       "RFC7471: OSPF Traffic Engineering (TE) Metric Extensions.
        RFC7810: IS-IS Traffic Engineering (TE) Metric Extensions.
        RFC7823: Performance-Based Path Selection for Explicitly
        Routed Label Switched Paths (LSPs) Using TE Metric
        Extensions";
   }

   typedef te-admin-status {
     type enumeration {
       enum up {
         description
           "Enabled.";
       }
       enum down {
         description
           "Disabled.";
       }
       enum testing {
         description
           "In some test mode.";
       }
       enum preparing-maintenance {
         description
           "Resource is disabled in the control plane to prepare for
            graceful shutdown for maintenance purposes.";
         reference
           "RFC5817: Graceful Shutdown in MPLS and Generalized MPLS
            Traffic Engineering Networks";
       }
       enum maintenance {
         description
           "Resource is disabled in the data plane for maintenance
            purposes.";
       }
     }
     description
       "Defines a type representing the administrative status of
        a TE resource.";
   }

   typedef te-global-id {
     type uint32;
     description
       "An identifier to uniquely identify an operator, which can be
        either a provider or a client.
        The definition of this type is taken from RFC6370 and RFC5003.
        This attribute type is used solely to provide a globally
        unique context for TE topologies.";
   }

   typedef te-link-access-type {
     type enumeration {
       enum point-to-point {
         description
           "The link is point-to-point.";
       }
       enum multi-access {
         description
           "The link is multi-access, including broacast and NBMA.";
       }
     }
     description
       "Defines a type representing the access type of a TE link.";
     reference
       "RFC3630: Traffic Engineering (TE) Extensions to OSPF
        Version 2.";
   }

   typedef te-node-id {
     type yang:dotted-quad;
     description
       "An identifier for a node in a topology.
        The identifier is represented as 32-bit unsigned integer in
        the dotted-quad notation.
        This attribute is mapped to Router ID in
        RFC3630, RFC5329, RFC5305, and RFC6119.";
   }

   typedef te-oper-status {
     type enumeration {
       enum up {
         description
         "Operational up.";
       }
       enum down {
         description
         "Operational down.";
       }
       enum testing {
         description
         "In some test mode.";
       }
       enum unknown {
         description
         "Status cannot be determined for some reason.";
       }
       enum preparing-maintenance {
         description
           "Resource is disabled in the control plane to prepare for
            graceful shutdown for maintenance purposes.";
         reference
           "RFC5817: Graceful Shutdown in MPLS and Generalized MPLS
            Traffic Engineering Networks";
       }
       enum maintenance {
         description
           "Resource is disabled in the data plane for maintenance
            purposes.";
       }
     }
     description
       "Defines a type representing the operational status of
        a TE resource.";
   }

   typedef te-recovery-status {
     type enumeration {
       enum normal {
         description
           "Both the recovery and working spans are fully
            allocated and active, data traffic is being
            transported over (or selected from) the working
            span, and no trigger events are reported.";
       }
       enum recovery-started {
         description
           "The recovery action has been started, but not completed.";
       }
       enum recovery-succeeded {
         description
           "The recovery action has succeeded. The working span has
            reported a failure/degrade condition and the user traffic
            is being transported (or selected) on the recovery span.";
       }
       enum recovery-failed {
         description
           "The recovery action has failed.";
       }
       enum reversion-started {
         description
           "The reversion has started.";
       }
       enum reversion-failed {
         description
           "The reversion has failed.";
       }
       enum recovery-unavailable {
         description
           "The recovery is unavailable -- either as a result of an
            operator Lockout command or a failure condition detected
            on the recovery span.";
       }
       enum recovery-admin {
         description
           "The operator has issued a command switching the user
            traffic to the recovery span.";
       }
       enum wait-to-restore {
         description
           "The recovery domain is recovering from a failuer/degrade
            condition on the working span that is being controlled by
            the Wait-to-Restore (WTR) timer.";
       }
     }
     description
       "Defines the status of a recovery action.";
     reference
       "RFC4427: Recovery (Protection and Restoration) Terminology
        for Generalized Multi-Protocol Label Switching (GMPLS).
        RFC6378: MPLS Transport Profile (MPLS-TP) Linear Protection";
   }

   typedef te-template-name {
     type string {
       pattern '/?([a-zA-Z0-9\-_.]+)(/[a-zA-Z0-9\-_.]+)*';
     }
     description
       "A type for the name of a TE node template or TE link
        template.";
   }

   typedef te-topology-event-type {
     type enumeration {
       enum "add" {
         value 0;
         description
           "A TE node or te-link has been added.";
       }
       enum "remove" {
         value 1;
         description
           "A TE node or te-link has been removed.";
       }
       enum "update" {
         value 2;
         description
           "A TE node or te-link has been updated.";
       }
     }
     description "TE  Event type for notifications";
   } // te-topology-event-type

   typedef te-topology-id {
     type string {
       pattern
         '([a-zA-Z0-9\-_.]+:)*'
       + '/?([a-zA-Z0-9\-_.]+)(/[a-zA-Z0-9\-_.]+)*';
     }
     description
       "An identifier for a topology.
        It is optional to have one or more prefixes at the begining,
        separated by colons. The prefixes can be the network-types,
        defined in ietf-network.yang, to help user to understand the
        topology better before further inquiry.";
   }

   typedef te-tp-id {
     type union {
       type uint32;          // Unnumbered
       type inet:ip-address; // IPv4 or IPv6 address
     }
     description
       "An identifier for a TE link endpoint on a node.
        This attribute is mapped to local or remote link identifier in
        RFC3630 and RFC5305.";
   }

   typedef admin-group {
     type binary {
       length 4;
     }
     description
       "Administrative group/Resource class/Color.";
   }

   typedef extended-admin-group {
     type binary;
     description
       "Extended administrative group/Resource class/Color.";
   }

   typedef admin-groups {
     type union {
       type admin-group;
       type extended-admin-group;
     }
     description "TE administrative group derived type";
   }

   typedef srlg {
     type uint32;
     description "SRLG type";
   }

   identity path-computation-srlg-type {
     description
       "Base identity for SRLG path computation";
   }

   identity srlg-ignore {
     base path-computation-srlg-type;
     description
       "Ignores SRLGs in path computation";
   }

   identity srlg-strict {
     base path-computation-srlg-type;
     description
       "Include strict SRLG check in path computation";
   }

   identity srlg-preferred {
     base path-computation-srlg-type;
     description
       "Include preferred SRLG check in path computation";
   }

   identity srlg-weighted {
     base path-computation-srlg-type;
     description
       "Include weighted SRLG check in path computation";
   }

   typedef te-metric {
     type uint32;
     description
       "TE link metric";
   }

   /**
    * TE performance metric groupings
    **/
   grouping performance-metric-container {
     description
       "A container containing performance metric attributes.";
     container performance-metric {
       description
         "Link performance information in real time.";
       reference
         "RFC7471: OSPF Traffic Engineering (TE) Metric Extensions.
          RFC7810: IS-IS Traffic Engineering (TE) Metric Extensions.
          RFC7823: Performance-Based Path Selection for Explicitly
          Routed Label Switched Paths (LSPs) Using TE Metric
          Extensions";
       container measurement {
         description
           "Measured performance metric values. Static configuration
            and manual overrides of these measurements are also
            allowed.";
         uses performance-metric-attributes;
       }
       container normality
       {
         description
           "Performance metric normality values.";
         uses performance-metric-normality-attributes;
       }
       uses performance-metric-throttle-container;
     }
   } // performance-metric-container

   grouping performance-metric-attributes {
     description
       "Link performance information in real time.";
     reference
       "RFC7471: OSPF Traffic Engineering (TE) Metric Extensions.
        RFC7810: IS-IS Traffic Engineering (TE) Metric Extensions.
        RFC7823: Performance-Based Path Selection for Explicitly
        Routed Label Switched Paths (LSPs) Using TE Metric
        Extensions";
     leaf unidirectional-delay {
       type uint32 {
         range 0..16777215;
       }
       description "Delay or latency in micro seconds.";
     }
     leaf unidirectional-min-delay {
       type uint32 {
         range 0..16777215;
       }
       description "Minimum delay or latency in micro seconds.";
     }
     leaf unidirectional-max-delay {
       type uint32 {
         range 0..16777215;
       }
       description "Maximum delay or latency in micro seconds.";
     }
     leaf unidirectional-delay-variation {
       type uint32 {
         range 0..16777215;
       }
       description "Delay variation in micro seconds.";
     }
     leaf unidirectional-packet-loss {
       type decimal64 {
         fraction-digits 6;
         range "0 .. 50.331642";
       }
       description
         "Packet loss as a percentage of the total traffic sent
          over a configurable interval. The finest precision is
          0.000003%.";
     }
     leaf unidirectional-residual-bandwidth {
       type rt-types:bandwidth-ieee-float32;
       description
         "Residual bandwidth that subtracts tunnel
          reservations from Maximum Bandwidth (or link capacity)
          [RFC3630] and provides an aggregated remainder across QoS
          classes.";
     }
     leaf unidirectional-available-bandwidth {
       type rt-types:bandwidth-ieee-float32;
       description
         "Available bandwidth that is defined to be residual
          bandwidth minus the measured bandwidth used for the
          actual forwarding of non-RSVP-TE LSP packets.  For a
          bundled link, available bandwidth is defined to be the
          sum of the component link available bandwidths.";
     }
     leaf unidirectional-utilized-bandwidth {
       type rt-types:bandwidth-ieee-float32;
       description
         "Bandwidth utilization that represents the actual
          utilization of the link (i.e. as measured in the router).
          For a bundled link, bandwidth utilization is defined to
          be the sum of the component link bandwidth
          utilizations.";
     }
   } // performance-metric-attributes

   grouping performance-metric-normality-attributes {
     description
       "Link performance metric normality attributes.";
     reference
       "RFC7471: OSPF Traffic Engineering (TE) Metric Extensions.
        RFC7810: IS-IS Traffic Engineering (TE) Metric Extensions.
        RFC7823: Performance-Based Path Selection for Explicitly
        Routed Label Switched Paths (LSPs) Using TE Metric
        Extensions";
     leaf unidirectional-delay {
       type te-types:performance-metric-normality;
       description "Delay normality.";
     }
     leaf unidirectional-min-delay {
       type te-types:performance-metric-normality;
       description "Minimum delay or latency normality.";
     }
     leaf unidirectional-max-delay {
       type te-types:performance-metric-normality;
       description "Maximum delay or latency normality.";
     }
     leaf unidirectional-delay-variation {
       type te-types:performance-metric-normality;
       description "Delay variation normality.";
     }
     leaf unidirectional-packet-loss {
       type te-types:performance-metric-normality;
       description "Packet loss normality.";
     }
     leaf unidirectional-residual-bandwidth {
       type te-types:performance-metric-normality;
       description "Residual bandwidth normality.";
     }
     leaf unidirectional-available-bandwidth {
       type te-types:performance-metric-normality;
       description "Available bandwidth normality.";
     }
     leaf unidirectional-utilized-bandwidth {
       type te-types:performance-metric-normality;
       description "Bandwidth utilization normality.";
     }
   } // performance-metric-normality-attributes

   grouping performance-metric-throttle-container {
     description
       "A container controlling performance metric throttle.";
     container throttle {
       must "suppression-interval >= measure-interval" {
         error-message
           "suppression-interval cannot be less then
            measure-interval.";
         description
           "Constraint on suppression-interval and
            measure-interval.";
       }
       description
         "Link performance information in real time.";
       reference
         "RFC7471: OSPF Traffic Engineering (TE) Metric Extensions.
          RFC7810: IS-IS Traffic Engineering (TE) Metric Extensions.
          RFC7823: Performance-Based Path Selection for Explicitly
          Routed Label Switched Paths (LSPs) Using TE Metric
          Extensions";
       leaf unidirectional-delay-offset {
         type uint32 {
           range 0..16777215;
         }
         description
           "Offset value to be added to the measured delay value.";
       }
       leaf measure-interval {
         type uint32;
         default 30;
         description
           "Interval in seconds to measure the extended metric
            values.";
       }
       leaf advertisement-interval {
         type uint32;
         description
           "Interval in seconds to advertise the extended metric
            values.";
       }
       leaf suppression-interval {
         type uint32 {
           range "1 .. max";
         }
         default 120;
         description
           "Interval in seconds to suppress advertising the extended
            metric values.";
       }
       container threshold-out {
         uses performance-metric-attributes;
         description
           "If the measured parameter falls outside an upper bound
            for all but the min delay metric (or lower bound for
            min-delay metric only) and the advertised value is not
            already outside that bound, anomalous announcement will be
            triggered.";
       }
       container threshold-in {
         uses performance-metric-attributes;
         description
           "If the measured parameter falls inside an upper bound
            for all but the min delay metric (or lower bound for
            min-delay metric only) and the advertised value is not
            already inside that bound, normal (anomalous-flag cleared)
            announcement will be triggered.";
       }
       container threshold-accelerated-advertisement {
         description
           "When the difference between the last advertised value and
            current measured value exceed this threshold, anomalous
            announcement will be triggered.";
         uses performance-metric-attributes;
       }
     }
   } // performance-metric-throttle-container

   /**
    * TE tunnel generic groupings
    **/

   /* Tunnel path selection parameters */
   /*** End of TE tunnel groupings ***/

   /**
    * TE interface generic groupings
    **/


/**************************************************************/
//TODO: FIXME: HENRY added begins
  identity te-path-numerical-property {
    description "Base TE path property type";
  }
  identity te-path-cost {
    base te-path-numerical-property;
    description "TE path property";
  }
  identity te-path-delay {
    base te-path-numerical-property;
    description "TE path property";
  }
  identity te-path-hop {
    base te-path-numerical-property;
    description "TE path property";
  }
  identity te-path-igp-metric {
    base te-path-numerical-property;
    description "TE path property";
  }
  identity te-path-metric {
    base te-path-numerical-property;
    description "TE path property";
  }

  typedef te-path-disjointness {
    type bits {
      bit node {
        position 0;
        description "Node disjoint.";
      }
      bit link {
        position 1;
        description "Link disjoint.";
      }
      bit srlg {
        position 2;
        description "SRLG (Shared Risk Link Group) disjoint.";
      }
    }
    description
      "Type of the resource disjointness for a TE tunnel path.";
    reference
      "RFC4872: RSVP-TE Extensions in Support of End-to-End
       Generalized Multi-Protocol Label Switching (GMPLS)
       Recovery";
  } // te-path-disjointness

  typedef te-bandwidth {
    type string {
      pattern
        '0[xX](0((\.0?)?[pP](\+)?0?|(\.0?))|'
      + '1(\.([\da-fA-F]{0,5}[02468aAcCeE]?)?)?[pP](\+)?(12[0-7]|'
      + '1[01]\d|0?\d?\d)?)|0[xX][\da-fA-F]{1,8}|\d+'
      + '(,(0[xX](0((\.0?)?[pP](\+)?0?|(\.0?))|'
      + '1(\.([\da-fA-F]{0,5}[02468aAcCeE]?)?)?[pP](\+)?(12[0-7]|'
      + '1[01]\d|0?\d?\d)?)|0[xX][\da-fA-F]{1,8}|\d+))*';
    }
    description
      "This is the generic bandwidth type that is a string containing
       a list of numbers separated by commas, with each of these
       number can be non-negative decimal, hex integer, or hex float:
       (dec | hex | float)[*(','(dec | hex | float))]
       For packet switching type, a float number is used, such as
       0x1p10.
       For OTN switching type, a list of integers can be used, such
       as '0,2,3,1', indicating 2 odu0's and 1 odu3.
       For DWDM, a list of pairs of slot number and width can be
       used, such as '0, 2, 3, 3', indicating a frequency slot 0 with
       slot width 2 and a frequency slot 3 with slot width 3.";
  } // te-bandwidth



//TODO: FIXME: HENRY added finish
/**************************************************************/

 }
