module test5 {
    namespace "test5:test";
    prefix test ;

    revision "2016-07-04" {
             description "Initial revision.";
    }
    leaf-list a-leaf {
       type int32;
     }
    leaf-list b-leaf {
       type int32;
     }
    
}
