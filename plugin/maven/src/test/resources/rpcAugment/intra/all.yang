module ietf-inet {

  namespace "yang:all";
  prefix "inet";
  yang-version 1;

  typedef ip-address {
     type int32;
  }
  
  leaf-list id {
    type string;
  }

  leaf mybits {
           type bits {
               bit disable-nagle {
                   position 0;
               }
               bit auto-sense-speed {
                   position 1;
               }
               bit Mb-only {
                   position 2;
               }
           }
       }

  container network {
      leaf network-ip {
          type ip-address;
      }
  }

  typedef leaf1 {
     type leafref {
         path "/network/network-ip";
     }
  }

  grouping link-details {
      leaf link-id {
          type int32;
      }
      container link {
          leaf port {
            type int32;
          }
  
          leaf-list port-id {
              type string;
          }
          list areas {
             key "name1";
             leaf name1 {
              type string;
             }
          }
      }
   }

   notification link-up {
        leaf link-id {
          type int32;
        }
  
        leaf-list link-name {
           type string;
        }
   }

   rpc get-port {
       input {
           leaf port {
              type int32;
            }
  
           leaf-list port-id {
              type string;
           }
           uses link-details;
       }
       output {
           container port {
                leaf port-number {
                   type enumeration {
                       enum zero-0;
                   }
                 }
                 leaf ip {
                  type ip-address;
                }
           }
       }
    }           
  
    augment /get-port/input {
       leaf port {
           type int32;
        }
    }      
   
}
