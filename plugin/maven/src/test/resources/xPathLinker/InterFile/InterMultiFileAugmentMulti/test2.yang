module test2 {  
    namespace "xpath:inter:multi";  
    prefix test2 ;  
      
    organization "";  
    contact "";  
       
    description   
        "Defines basic service types for L3VPN service.";  
       
    revision "2015-12-16" {  
        reference "";  
    }  

    container cont1 {
       leaf leaf5 {
          type int32;
       }
       container cont2 {
          leaf leaf6 {
             type int32;
          }
       }
    }

    augment /cont1/cont2 {
        container cont3 {
            leaf leaf7 {
              type string;
            }
        }
    }
}
