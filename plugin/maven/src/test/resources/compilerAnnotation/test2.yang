module test1 {  
    namespace "test1:test1";  
    prefix test1 ;  

    import test {
       prefix test;
    }
    organization "";  
    contact "";  

    description   
       "Defines basic service types for L3VPN service.";  

    revision "2015-12-16" {  
       reference "";  
    }

    ca:compiler-annotation /test:list1 {
        ds:app-data-structure "Map";
    }
}
